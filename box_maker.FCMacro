# -*- coding: utf-8 -*-

# This script creates a dialog to generate a hollow box (a rectangular prism
# with a hollowed-out center) in FreeCAD.
# The user can define the outer dimensions, inner dimensions, and also
# add fillets to the outer corners and a chamfer to the bottom edges.

__title__   = "Box Maker"
__author__  = "ssj71"
__version__ = "2.3"
__date__    = "2025-09-10"

import FreeCAD as App
import FreeCADGui as Gui
import Part
import math
from PySide import QtGui, QtCore

# A data container to hold all the box parameters
class BoxParameters:
    def __init__(self, outer_l, outer_w, outer_h, inner_l, inner_w, inner_h,
                 outer_sides_fillet_enabled, outer_sides_fillet_r,
                 outer_top_fillet_enabled, outer_top_fillet_r,
                 chamfer_enabled, chamfer_s,
                 inner_sides_fillet_enabled, inner_bottom_fillet_enabled,
                 inner_sides_fillet_r, inner_bottom_fillet_r,
                 lid_enabled, clearance, lid_thickness,
                 finger_hole_front_enabled, finger_hole_back_enabled,
                 finger_hole_left_enabled, finger_hole_right_enabled,
                 finger_hole_bottom_enabled, finger_hole_radius):
        self.outer_l = outer_l
        self.outer_w = outer_w
        self.outer_h = outer_h
        self.inner_l = inner_l
        self.inner_w = inner_w
        self.inner_h = inner_h
        self.outer_sides_fillet_enabled = outer_sides_fillet_enabled
        self.outer_sides_fillet_r = outer_sides_fillet_r
        self.outer_top_fillet_enabled = outer_top_fillet_enabled
        self.outer_top_fillet_r = outer_top_fillet_r
        self.chamfer_enabled = chamfer_enabled
        self.chamfer_s = chamfer_s
        self.inner_sides_fillet_enabled = inner_sides_fillet_enabled
        self.inner_bottom_fillet_enabled = inner_bottom_fillet_enabled
        self.inner_sides_fillet_r = inner_sides_fillet_r
        self.inner_bottom_fillet_r = inner_bottom_fillet_r
        self.lid_enabled = lid_enabled
        self.clearance = clearance
        self.lid_thickness = lid_thickness
        self.finger_hole_front_enabled = finger_hole_front_enabled
        self.finger_hole_back_enabled = finger_hole_back_enabled
        self.finger_hole_left_enabled = finger_hole_left_enabled
        self.finger_hole_right_enabled = finger_hole_right_enabled
        self.finger_hole_bottom_enabled = finger_hole_bottom_enabled
        self.finger_hole_radius = finger_hole_radius

# Define the main dialog class
class HollowBoxDialog(QtGui.QDialog):
    def __init__(self):
        super(HollowBoxDialog, self).__init__()
        self.initUI()
        
    def initUI(self):
        # Set up the window title and layout
        self.setWindowTitle("Create Hollow Box")
        self.setWindowFlags(QtCore.Qt.WindowStaysOnTopHint)
        self.mainLayout = QtGui.QGridLayout(self)
        
        # --- Outer Dimensions Group Box ---
        outerGroupBox = QtGui.QGroupBox("Outer Dimensions", self)
        outerLayout = QtGui.QGridLayout(outerGroupBox)
        
        # Outer Length
        outerLengthLabel = QtGui.QLabel("Length:", self)
        self.outerLengthEdit = QtGui.QLineEdit(self)
        self.outerLengthEdit.setText("95.0")
        outerLayout.addWidget(outerLengthLabel, 0, 0)
        outerLayout.addWidget(self.outerLengthEdit, 0, 1)
        
        # Outer Width
        outerWidthLabel = QtGui.QLabel("Width:", self)
        self.outerWidthEdit = QtGui.QLineEdit(self)
        self.outerWidthEdit.setText("68.5")
        outerLayout.addWidget(outerWidthLabel, 1, 0)
        outerLayout.addWidget(self.outerWidthEdit, 1, 1)
        
        # Outer Height
        outerHeightLabel = QtGui.QLabel("Height:", self)
        self.outerHeightEdit = QtGui.QLineEdit(self)
        self.outerHeightEdit.setText("34.0")
        outerLayout.addWidget(outerHeightLabel, 2, 0)
        outerLayout.addWidget(self.outerHeightEdit, 2, 1)
        
        self.mainLayout.addWidget(outerGroupBox, 0, 0)
        
        # --- Outer Fillet & Chamfer Options Group Box ---
        outerOptionsGroupBox = QtGui.QGroupBox("Outer Fillet & Chamfer Options", self)
        outerOptionsLayout = QtGui.QGridLayout(outerOptionsGroupBox)

        # Fillet sides option
        self.outerSidesFilletCheck = QtGui.QCheckBox("Fillet outer vertical corners", self)
        self.outerSidesFilletCheck.setChecked(True)
        outerOptionsLayout.addWidget(self.outerSidesFilletCheck, 0, 0)

        outerSidesFilletRadiusLabel = QtGui.QLabel("Side Radius:", self)
        self.outerSidesFilletRadiusEdit = QtGui.QLineEdit(self)
        self.outerSidesFilletRadiusEdit.setText("3.0")
        outerOptionsLayout.addWidget(outerSidesFilletRadiusLabel, 0, 1)
        outerOptionsLayout.addWidget(self.outerSidesFilletRadiusEdit, 0, 2)
        
        # Fillet top option
        self.outerTopFilletCheck = QtGui.QCheckBox("Fillet outer top edges", self)
        self.outerTopFilletCheck.setChecked(False)
        outerOptionsLayout.addWidget(self.outerTopFilletCheck, 1, 0)

        outerTopFilletRadiusLabel = QtGui.QLabel("Top Radius:", self)
        self.outerTopFilletRadiusEdit = QtGui.QLineEdit(self)
        self.outerTopFilletRadiusEdit.setText("1.0")
        outerOptionsLayout.addWidget(outerTopFilletRadiusLabel, 1, 1)
        outerOptionsLayout.addWidget(self.outerTopFilletRadiusEdit, 1, 2)

        # Chamfer option
        self.chamferCheck = QtGui.QCheckBox("Chamfer bottom edge (30°)", self)
        self.chamferCheck.setChecked(True)
        outerOptionsLayout.addWidget(self.chamferCheck, 2, 0)
        
        chamferSizeLabel = QtGui.QLabel("Chamfer Size:", self)
        self.chamferSizeEdit = QtGui.QLineEdit(self)
        self.chamferSizeEdit.setText("1.0")
        outerOptionsLayout.addWidget(chamferSizeLabel, 2, 1)
        outerOptionsLayout.addWidget(self.chamferSizeEdit, 2, 2)

        self.mainLayout.addWidget(outerOptionsGroupBox, 1, 0)
        
        # --- Inner Dimensions Group Box ---
        innerGroupBox = QtGui.QGroupBox("Inner Dimensions", self)
        innerLayout = QtGui.QGridLayout(innerGroupBox)
        
        # Inner Length
        innerLengthLabel = QtGui.QLabel("Length:", self)
        self.innerLengthEdit = QtGui.QLineEdit(self)
        self.innerLengthEdit.setText("91.0")
        innerLayout.addWidget(innerLengthLabel, 0, 0)
        innerLayout.addWidget(self.innerLengthEdit, 0, 1)
        
        # Inner Width
        innerWidthLabel = QtGui.QLabel("Width:", self)
        self.innerWidthEdit = QtGui.QLineEdit(self)
        self.innerWidthEdit.setText("64.5")
        innerLayout.addWidget(innerWidthLabel, 1, 0)
        innerWidthLabel.setToolTip("Must be less than Outer Width")
        innerLayout.addWidget(self.innerWidthEdit, 1, 1)
        
        # Inner Height
        innerHeightLabel = QtGui.QLabel("Height:", self)
        self.innerHeightEdit = QtGui.QLineEdit(self)
        self.innerHeightEdit.setText("30.0")
        innerLayout.addWidget(innerHeightLabel, 2, 0)
        innerHeightLabel.setToolTip("Must be less than Outer Height")
        innerLayout.addWidget(self.innerHeightEdit, 2, 1)
        
        self.mainLayout.addWidget(innerGroupBox, 2, 0)
        
        # --- Inner Fillet Options Group Box ---
        innerOptionsGroupBox = QtGui.QGroupBox("Inner Fillet Options", self)
        innerOptionsLayout = QtGui.QGridLayout(innerOptionsGroupBox)

        # Fillet inner sides
        self.innerSidesFilletCheck = QtGui.QCheckBox("Fillet inner sides", self)
        self.innerSidesFilletCheck.setChecked(True)
        innerOptionsLayout.addWidget(self.innerSidesFilletCheck, 0, 0)

        innerSidesFilletRadiusLabel = QtGui.QLabel("Side Radius:", self)
        self.innerSidesFilletRadiusEdit = QtGui.QLineEdit(self)
        self.innerSidesFilletRadiusEdit.setText("2.0")
        innerOptionsLayout.addWidget(innerSidesFilletRadiusLabel, 0, 1)
        innerOptionsLayout.addWidget(self.innerSidesFilletRadiusEdit, 0, 2)

        # Fillet inner bottom edges
        self.innerBottomFilletCheck = QtGui.QCheckBox("Fillet inner bottom edges", self)
        self.innerBottomFilletCheck.setChecked(True)
        innerOptionsLayout.addWidget(self.innerBottomFilletCheck, 1, 0)
        
        innerBottomFilletRadiusLabel = QtGui.QLabel("Bottom Radius:", self)
        self.innerBottomFilletRadiusEdit = QtGui.QLineEdit(self)
        self.innerBottomFilletRadiusEdit.setText("2.0")
        innerOptionsLayout.addWidget(innerBottomFilletRadiusLabel, 1, 1)
        innerOptionsLayout.addWidget(self.innerBottomFilletRadiusEdit, 1, 2)

        self.mainLayout.addWidget(innerOptionsGroupBox, 3, 0)

        # --- Finger Hole Options Group Box ---
        fingerHoleGroupBox = QtGui.QGroupBox("Finger Hole Options", self)
        fingerHoleLayout = QtGui.QGridLayout(fingerHoleGroupBox)

        self.fingerHoleFrontCheck = QtGui.QCheckBox("Front", self)
        fingerHoleLayout.addWidget(self.fingerHoleFrontCheck, 0, 0)
        self.fingerHoleBackCheck = QtGui.QCheckBox("Back", self)
        fingerHoleLayout.addWidget(self.fingerHoleBackCheck, 0, 1)
        self.fingerHoleLeftCheck = QtGui.QCheckBox("Left", self)
        fingerHoleLayout.addWidget(self.fingerHoleLeftCheck, 1, 0)
        self.fingerHoleRightCheck = QtGui.QCheckBox("Right", self)
        fingerHoleLayout.addWidget(self.fingerHoleRightCheck, 1, 1)
        self.fingerHoleBottomCheck = QtGui.QCheckBox("Bottom", self)
        fingerHoleLayout.addWidget(self.fingerHoleBottomCheck, 2, 0)

        fingerHoleRadiusLabel = QtGui.QLabel("Radius:", self)
        self.fingerHoleRadiusEdit = QtGui.QLineEdit(self)
        self.fingerHoleRadiusEdit.setText("10.0")
        fingerHoleLayout.addWidget(fingerHoleRadiusLabel, 3, 0)
        fingerHoleLayout.addWidget(self.fingerHoleRadiusEdit, 3, 1)

        self.mainLayout.addWidget(fingerHoleGroupBox, 4, 0)
        
        # --- Lid Options Group Box ---
        lidOptionsGroupBox = QtGui.QGroupBox("Lid Options", self)
        lidOptionsLayout = QtGui.QGridLayout(lidOptionsGroupBox)
        
        self.lidCheck = QtGui.QCheckBox("Create a lid", self)
        self.lidCheck.setChecked(True)
        lidOptionsLayout.addWidget(self.lidCheck, 0, 0)
        
        lidThicknessLabel = QtGui.QLabel("Lid Thickness:", self)
        self.lidThicknessEdit = QtGui.QLineEdit(self)
        self.lidThicknessEdit.setText("2.0")
        lidOptionsLayout.addWidget(lidThicknessLabel, 1, 0)
        lidOptionsLayout.addWidget(self.lidThicknessEdit, 1, 1)
        
        clearanceLabel = QtGui.QLabel("Clearance:", self)
        self.clearanceEdit = QtGui.QLineEdit(self)
        self.clearanceEdit.setText("0.1")
        lidOptionsLayout.addWidget(clearanceLabel, 2, 0)
        lidOptionsLayout.addWidget(self.clearanceEdit, 2, 1)
        
        self.mainLayout.addWidget(lidOptionsGroupBox, 5, 0)
        
        # --- Buttons ---
        buttonBox = QtGui.QDialogButtonBox(QtGui.QDialogButtonBox.Ok | QtGui.QDialogButtonBox.Cancel, self)
        self.mainLayout.addWidget(buttonBox, 6, 0)
        buttonBox.accepted.connect(self.accept)
        buttonBox.rejected.connect(self.reject)
        
    def getValues(self):
        try:
            # Parse the input values from the text fields
            outer_l = float(self.outerLengthEdit.text())
            outer_w = float(self.outerWidthEdit.text())
            outer_h = float(self.outerHeightEdit.text())
            inner_l = float(self.innerLengthEdit.text())
            inner_w = float(self.innerWidthEdit.text())
            inner_h = float(self.innerHeightEdit.text())
            
            outer_sides_fillet_enabled = self.outerSidesFilletCheck.isChecked()
            outer_top_fillet_enabled = self.outerTopFilletCheck.isChecked()
            chamfer_enabled = self.chamferCheck.isChecked()
            inner_sides_fillet_enabled = self.innerSidesFilletCheck.isChecked()
            inner_bottom_fillet_enabled = self.innerBottomFilletCheck.isChecked()
            lid_enabled = self.lidCheck.isChecked()
            finger_hole_front_enabled = self.fingerHoleFrontCheck.isChecked()
            finger_hole_back_enabled = self.fingerHoleBackCheck.isChecked()
            finger_hole_left_enabled = self.fingerHoleLeftCheck.isChecked()
            finger_hole_right_enabled = self.fingerHoleRightCheck.isChecked()
            finger_hole_bottom_enabled = self.fingerHoleBottomCheck.isChecked()
            
            outer_sides_fillet_r = 0.0
            outer_top_fillet_r = 0.0
            chamfer_s = 0.0
            inner_sides_fillet_r = 0.0
            inner_bottom_fillet_r = 0.0
            clearance = 0.0
            lid_thickness = 0.0
            finger_hole_radius = 0.0

            if outer_sides_fillet_enabled:
                outer_sides_fillet_r = float(self.outerSidesFilletRadiusEdit.text())
            if outer_top_fillet_enabled:
                outer_top_fillet_r = float(self.outerTopFilletRadiusEdit.text())
            if chamfer_enabled:
                chamfer_s = float(self.chamferSizeEdit.text())
            if inner_sides_fillet_enabled:
                inner_sides_fillet_r = float(self.innerSidesFilletRadiusEdit.text())
            if inner_bottom_fillet_enabled:
                inner_bottom_fillet_r = float(self.innerBottomFilletRadiusEdit.text())
            if lid_enabled:
                clearance = float(self.clearanceEdit.text())
                lid_thickness = float(self.lidThicknessEdit.text())
            if (finger_hole_front_enabled or finger_hole_back_enabled or
                finger_hole_left_enabled or finger_hole_right_enabled or
                finger_hole_bottom_enabled):
                finger_hole_radius = float(self.fingerHoleRadiusEdit.text())

            # Basic input validation
            if outer_l <= 0 or outer_w <= 0 or outer_h <= 0 or inner_l <= 0 or inner_w <= 0 or inner_h <= 0:
                QtGui.QMessageBox.critical(self, "Input Error", "All dimensions must be greater than zero.")
                return None
            
            if inner_l >= outer_l or inner_w >= outer_w or inner_h >= outer_h:
                QtGui.QMessageBox.critical(self, "Input Error", "Inner dimensions must be smaller than outer dimensions.")
                return None
            
            if outer_sides_fillet_enabled and outer_sides_fillet_r <= 0:
                QtGui.QMessageBox.critical(self, "Input Error", "Outer sides fillet radius must be greater than zero.")
                return None
            
            if outer_top_fillet_enabled and outer_top_fillet_r <= 0:
                QtGui.QMessageBox.critical(self, "Input Error", "Outer top fillet radius must be greater than zero.")
                return None
            
            if chamfer_enabled and chamfer_s <= 0:
                QtGui.QMessageBox.critical(self, "Input Error", "Chamfer size must be greater than zero.")
                return None
            
            if inner_sides_fillet_enabled and inner_sides_fillet_r <= 0:
                QtGui.QMessageBox.critical(self, "Input Error", "Inner sides fillet radius must be greater than zero.")
                return None
            
            if inner_bottom_fillet_enabled and inner_bottom_fillet_r <= 0:
                QtGui.QMessageBox.critical(self, "Input Error", "Inner bottom fillet radius must be greater than zero.")
                return None
            
            if lid_enabled and (clearance <= 0 or lid_thickness <= 0):
                QtGui.QMessageBox.critical(self, "Input Error", "Lid clearance and thickness must be greater than zero.")
                return None
            
            if finger_hole_radius <= 0 and (finger_hole_front_enabled or finger_hole_back_enabled or
                                             finger_hole_left_enabled or finger_hole_right_enabled or
                                             finger_hole_bottom_enabled):
                QtGui.QMessageBox.critical(self, "Input Error", "Finger hole radius must be greater than zero if any finger holes are enabled.")
                return None

            return BoxParameters(outer_l, outer_w, outer_h, inner_l, inner_w, inner_h,
                                 outer_sides_fillet_enabled, outer_sides_fillet_r,
                                 outer_top_fillet_enabled, outer_top_fillet_r,
                                 chamfer_enabled, chamfer_s,
                                 inner_sides_fillet_enabled, inner_bottom_fillet_enabled,
                                 inner_sides_fillet_r, inner_bottom_fillet_r,
                                 lid_enabled, clearance, lid_thickness,
                                 finger_hole_front_enabled, finger_hole_back_enabled,
                                 finger_hole_left_enabled, finger_hole_right_enabled,
                                 finger_hole_bottom_enabled, finger_hole_radius)
        except ValueError:
            QtGui.QMessageBox.critical(self, "Input Error", "Please enter valid numbers for all dimensions.")
            return None

def fillet_edges(box, radius, edge_type):
    """
    Applies a fillet to a list of edges on a given Part.Shape based on a type.
    
    Args:
        box (Part.Shape): The Part.Shape to modify.
        radius (float): The fillet radius.
        edge_type (str): The type of edges to fillet ("sides", "bottom", or "top").
    
    Returns:
        Part.Shape: The new shape after the fillet operation, or the original
                    shape if the operation fails.
    """
    edges_to_fillet = []
    if edge_type == "sides":
        for edge in box.Edges:
            if not math.isclose(edge.Vertexes[0].Point.z, edge.Vertexes[1].Point.z):
                edges_to_fillet.append(edge)
    elif edge_type == "bottom":
        for edge in box.Edges:
            if math.isclose(edge.Vertexes[0].Point.z, 0.0) and math.isclose(edge.Vertexes[1].Point.z, 0.0):
                edges_to_fillet.append(edge)
    elif edge_type == "top":
        z_max = box.BoundBox.ZMax
        for edge in box.Edges:
            if math.isclose(edge.Vertexes[0].Point.z, z_max) and math.isclose(edge.Vertexes[1].Point.z, z_max):
                edges_to_fillet.append(edge)
    
    if not edges_to_fillet:
        return box
    try:
        filleted_box = box.makeFillet(radius, edges_to_fillet)
        return filleted_box
    except:
        App.Console.PrintError(f"Failed to create {edge_type} fillet. Radius may be too large.")
        return box

def chamfer_bottom(box, size):
    """
    Applies a 30-degree chamfer to the bottom of a Part.Shape.
    
    Args:
        box (Part.Shape): The Part.Shape to modify.
        size (float): The horizontal size of the chamfer.
    
    Returns:
        Part.Shape: The new shape after the chamfer operation, or the original
                    shape if the operation fails.
    """
    edges_to_chamfer = []
    for edge in box.Edges:
            if math.isclose(edge.Vertexes[0].Point.z, 0.0) and math.isclose(edge.Vertexes[1].Point.z, 0.0):
                edges_to_chamfer.append(edge)
    try:
        # For a 30-degree chamfer, d2 = d1 / tan(30)
        chamfer_d2 = size / math.tan(math.radians(30))
        chamfered_box = box.makeChamfer(chamfer_d2, size, edges_to_chamfer)
        return chamfered_box
    except Exception as e:
        App.Console.PrintError("Failed to create chamfer. Size may be too large or there was another error.")
        App.Console.PrintError(str(e))
        return box

def create_lid(params, tool=False):
    """
    Creates a lid for the hollow box with a beveled base for a secure fit.
    
    Args:
        params (BoxParameters): The parameters from the dialog.
        tool (Boolean): Whether to size the lid as a cutting tool.
    """
    # Create the main body of the lid
    #currently the rim that holds the lid in place is 1mm wide
    lid_l = params.outer_l - 1*params.lid_thickness
    lid_w = params.outer_w - 2*params.lid_thickness
    lid_h = params.lid_thickness
    if not tool:
        lid_l -= 2 * params.clearance
        lid_w -= 2 * params.clearance
    
    lid_body = Part.makeBox(lid_l, lid_w, lid_h)

    # Chamfer the top edges to create the beveled edge
    chamfer_d1 = params.lid_thickness - .01
    chamfer_d2 = chamfer_d1 / math.sqrt(3)
    
    bevel_edges_to_chamfer = []
    for edge in lid_body.Edges:
        if math.isclose(edge.Vertexes[0].Point.z, params.lid_thickness) and math.isclose(edge.Vertexes[1].Point.z, params.lid_thickness):
            bevel_edges_to_chamfer.append(edge)
    try:
        chamfered_bevel = lid_body.makeChamfer(chamfer_d1, chamfer_d2, bevel_edges_to_chamfer[1:])
    except Exception as e:
        App.Console.PrintError("Failed to create chamfered bevel on the lid. Clearance may be too large.")
        print(str(e))
        return

    return chamfered_bevel

def create_finger_holes(params):
    """
    Cuts finger holes into the box based on user selection.
    
    Args:
        params (BoxParameters): The parameters from the dialog.
    
    Returns:
        Part.Shape: The shape to use for cutting.
    """
    
    # Finger hole cutter dimensions
    radius = params.finger_hole_radius
    height = params.outer_h + 2  # A bit longer than height to ensure a clean cut
    
    # Common position for the center of the cylinder's face
    y_center = params.inner_w / 2
    x_center = params.inner_l / 2

    list_of_cutters = []

    # Front face cutout
    if params.finger_hole_front_enabled:
        cutter = Part.makeCylinder(radius, height)
        cutter.Placement.Base = App.Vector(x_center, 0, -1)
        list_of_cutters.append(cutter)
        
    # Back face cutout
    if params.finger_hole_back_enabled:
        cutter = Part.makeCylinder(radius, height)
        cutter.Placement.Base = App.Vector(x_center, params.inner_w, -1)
        list_of_cutters.append(cutter)

    # Left face cutout
    if params.finger_hole_left_enabled:
        cutter = Part.makeCylinder(radius, height)
        cutter.Placement.Base = App.Vector(0, y_center, -1)
        list_of_cutters.append(cutter)

    # Right face cutout
    if params.finger_hole_right_enabled:
        cutter = Part.makeCylinder(radius, height)
        cutter.Placement.Base = App.Vector(params.inner_l, y_center, -1)
        list_of_cutters.append(cutter)

    # Bottom face cutout
    if params.finger_hole_bottom_enabled:
        cutter = Part.makeCylinder(radius, height)
        cutter.Placement.Base = App.Vector(x_center, y_center, -1)
        list_of_cutters.append(cutter)

    return Part.makeCompound(list_of_cutters)

def run():
    # Create an instance of the dialog
    dialog = HollowBoxDialog()
    
    # Show the dialog and check if the user clicked OK
    if dialog.exec_():
        params = dialog.getValues()
        if params:
            # use the current document for the box
            doc = App.ActiveDocument
            
            # Create the outer box
            outer_box_part = Part.makeBox(params.outer_l, params.outer_w, params.outer_h)
            
            # Apply fillet and chamfer operations if enabled
            if params.chamfer_enabled:
                outer_box_part = chamfer_bottom(outer_box_part, params.chamfer_s)

            if params.outer_sides_fillet_enabled:
                outer_box_part = fillet_edges(outer_box_part, params.outer_sides_fillet_r, "sides")
            
            if params.outer_top_fillet_enabled:
                outer_box_part = fillet_edges(outer_box_part, params.outer_top_fillet_r, "top")
            
            
            # Create a new object in the document for the modified outer box
            outer_box_obj = doc.addObject("Part::Feature", "OuterBox")
            outer_box_obj.Shape = outer_box_part
            
            # Create the inner box
            inner_box_part = Part.makeBox(params.inner_l, params.inner_w, params.inner_h)

            # Find and fillet inner edges if enabled
            if params.inner_sides_fillet_enabled:
                inner_box_part = fillet_edges(inner_box_part, params.inner_sides_fillet_r, "sides")
            
            if params.inner_bottom_fillet_enabled:
                inner_box_part = fillet_edges(inner_box_part, params.inner_bottom_fillet_r, "bottom")

            # Position the inner box to be centered within the outer box
            x_pos = (params.outer_l - params.inner_l) / 2
            y_pos = (params.outer_w - params.inner_w) / 2
            z_pos = (params.outer_h - params.inner_h)
            if params.lid_enabled:
                z_pos -= params.lid_thickness
            inner_box_part.Placement.Base = App.Vector(x_pos, y_pos, z_pos)
            
            # Subtract the inner box from the outer box to create the hollow shape
            hollow_box = doc.addObject("Part::Cut", "HollowBox")
            hollow_box.Base = outer_box_obj
            hollow_box.Tool = doc.addObject("Part::Feature", "InnerBox")
            hollow_box.Tool.Shape = inner_box_part
            
            if params.lid_enabled:
                lid = create_lid(params)
                if lid is not None:
                    lid_obj = doc.addObject("Part::Feature", "Lid")
                    lid_obj.Shape = lid
                    lid_obj.Placement.Base = App.Vector(0, params.outer_w + 2, 0)
                cutter = create_lid(params, tool=True)
                if cutter is not None:
                    cut_obj = doc.addObject("Part::Feature", "LidCut")
                    cut_obj.Shape = cutter
                    cut_obj.Placement.Base = App.Vector(0, params.lid_thickness, params.outer_h - params.lid_thickness)
                    hollow_box_w_lid = doc.addObject("Part::Cut", "HollowBoxWLid")
                    hollow_box_w_lid.Base = hollow_box
                    hollow_box_w_lid.Tool = cut_obj
                    hollow_box = hollow_box_w_lid
            
            # Add finger holes if selected
            if (params.finger_hole_front_enabled or params.finger_hole_back_enabled or
                params.finger_hole_left_enabled or params.finger_hole_right_enabled or
                params.finger_hole_bottom_enabled):
                
                finger_holes = create_finger_holes(params)
                if finger_holes is not None:
                    cut_obj = doc.addObject("Part::Feature", "HoleCut")
                    cut_obj.Shape = finger_holes
                    cut_obj.Placement.Base = App.Vector((params.outer_l - params.inner_l) / 2,
                                                        (params.outer_w - params.inner_w) / 2,
                                                        0)
                    hollow_box_w_hole = doc.addObject("Part::Cut", "HollowBoxWLid")
                    hollow_box_w_hole.Base = hollow_box
                    hollow_box_w_hole.Tool = cut_obj
                    hollow_box = hollow_box_w_hole

            # Recompute the document to show the result
            doc.recompute()
            Gui.SendMsgToActiveView("ViewFit")

# Run the script when the macro is executed
run()
